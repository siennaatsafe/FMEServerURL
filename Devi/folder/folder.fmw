FME workspace folder.fmw
Title: Concatenate published parameters
Description: This workspace shows how to configure a published parameter to include the value of another published or private parameter. This example shows how you can configure a workspace to prompt for a value and then use that value as part of a database where clause. 
If the where clause looks like the following:
ROAD_CATEGORY = 'MAJOR'
Then a published parameter would be created to prompt for the the value MAJOR. That parameter would then be referenced within a private parameter to create the full where clause. The private parameter value would appear like so:
ROAD_CATEGORY = 'MAJOR'
Usage: Follow these instructions to try out the workspaces:
    Click File > Prompt and Run > enter 'MAJOR'. 
    Run it again and enter 'MINOR'. Note the different number of features read. 
    In the Navigator, expand the road_attrs Reader > Parameters, right click the WHERE Clause parameter and select Edit Definition to see how it is configured.
History: 2011-01-10,Aaron Koning,Created

Parameters:
- PARAMETER =   # Select a File

Readers:
- MDB_ADO_1: MDB_ADO from $(FME_MF_DIR)Concatenate published parameters/1/GPS/road_attrs.mdb

major_roads (reader MDB_ADO_1)
    attributes: ROAD_ID text(8), TYPE_CODE text(8), PRIMARY_DIRECTION text(4), ROAD_CATEGORY text(20), ROAD_NAME text(40)
    -> Logger
Logger
    MAXCOORDS = 20
    MAXFEATS = 20
    MESSAGE = Feature is:
